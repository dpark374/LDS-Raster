FME workspace geotiff2none.fmw

Parameters:
- SourceDataset_GEOTIFF = $(FME_MF_DIR)NZ4633_oldbound.tif   # Source GeoTIFF File(s)
- DestDataset_GEOTIFF = C:\DB\LDS_Raster   # Destination GeoTIFF Folder

Readers:
- GEOTIFF_1: GEOTIFF from $(SourceDataset_GEOTIFF)

Writers:
- GEOTIFF_2: GEOTIFF to $(DestDataset_GEOTIFF)

GEOTIFF (reader GEOTIFF_1)
    -> Reprojector
Reprojector
    DEST = EPSG:4326
    INTERPOLATION_TYPE_NAME = Nearest Neighbor
    RASTER_CELL_SIZE = Preserve Cells
    RASTER_TOLERANCE = 0.0
    SOURCE = Read from feature
    REPROJECTED -> fme_basename+1 (writer GEOTIFF_2)
fme_basename+1 (writer GEOTIFF_2)
Inspector
